(defun C:CIRCLE ( / c rad p1 p2)
  (setq c (getpoint "\nChoose a center: "))
  (setq rad (getdist c "\nChoose a radius: "))
  (command "circle" c rad)
  (setq p1 (list (- (car c) rad) (+ (cadr c) rad)))
  (setq p2 (list (+ (car c) rad) (- (cadr c) rad)))
  (command "rectang" p1 p2)
  (princ)
  )
